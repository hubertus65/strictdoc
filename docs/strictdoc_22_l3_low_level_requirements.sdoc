[DOCUMENT]
MID: 6a9745098a87daf19a7c487f89f39640
TITLE: StrictDoc Low-Level Requirements Specification (L3)
VERSION: Git commit: @GIT_VERSION, Git branch: @GIT_BRANCH
DATE: @GIT_COMMIT_DATETIME
PREFIX: SDOC-LLR-
OPTIONS:
  ENABLE_MID: True

[GRAMMAR]
ELEMENTS:
- TAG: SECTION
  PROPERTIES:
    IS_COMPOSITE: True
    VIEW_STYLE: Narrative
  FIELDS:
  - TITLE: MID
    TYPE: String
    REQUIRED: False
  - TITLE: UID
    TYPE: String
    REQUIRED: False
  - TITLE: TITLE
    TYPE: String
    REQUIRED: True
- TAG: TEXT
  FIELDS:
  - TITLE: MID
    TYPE: String
    REQUIRED: True
  - TITLE: UID
    TYPE: String
    REQUIRED: False
  - TITLE: STATEMENT
    TYPE: String
    REQUIRED: False
- TAG: REQUIREMENT
  PROPERTIES:
    VIEW_STYLE: Table
  FIELDS:
  - TITLE: MID
    TYPE: String
    REQUIRED: False
  - TITLE: UID
    TYPE: String
    REQUIRED: False
  - TITLE: STATUS
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  RELATIONS:
  - TYPE: Parent
  - TYPE: File

[TEXT]
MID: 1ea652f0284940b6913a0a224492759f
STATEMENT: >>>
The level 3 low-level requirements specification of StrictDoc (L3/LLR) is
derived from StrictDoc's L2 high-level (L2/HLR) requirements specification. The
purpose of L3/LLR is to provide the lowest-level requirements from which
StrictDoc's source code can be directly implemented without further information.

It is at the L3 level that the StrictDoc requirements are specified for the
actual software implementers, including both the StrictDoc developers and AI
agents such as Codex. At the same time, the L2/HLR requirements provide the
framework for the WHAT and WHY of the implementation instructions that are
specified by this L3/LLR.

NOTE: This specification level is under construction. Many L2/HLR requirements
will be gradually moved to be here at the L3/HLR level.
<<<

[[SECTION]]
MID: 408105d13e234f8aa73d017404eb5349
TITLE: Markdown text markup

[REQUIREMENT]
MID: 34246811634c493dbc771ae4c8bc3b14
UID: SDOC-LLR-183
STATUS: Active
TITLE: Read Markdown markup
STATEMENT: >>>
StrictDoc shall support reading Markdown files into in-memory SDoc documents.
<<<
RELATIONS:
- TYPE: Parent
  VALUE: SDOC-SRS-202

[REQUIREMENT]
MID: 476d094833ac4b02af1d72ad27710b36
UID: SDOC-LLR-197
STATUS: Active
TITLE: Write Markdown markup
STATEMENT: >>>
StrictDoc shall support writing in-memory SDoc documents to Markdown files.
<<<
RELATIONS:
- TYPE: Parent
  VALUE: SDOC-SRS-202

[REQUIREMENT]
MID: bc3b1411634c493dbc771ae4c8bc3b14
UID: SDOC-LLR-192
STATUS: Active
TITLE: Markdown files discovery
STATEMENT: >>>
StrictDoc shall discover Markdown files ``*.md`` and ``*.markdown`` using the
same mechanism as used for SDoc files.
<<<
RELATIONS:
- TYPE: Parent
  VALUE: SDOC-SRS-202
- TYPE: Parent
  VALUE: SDOC-SRS-115

[REQUIREMENT]
MID: 245378eed60245378de2e099facd196d
UID: SDOC-LLR-196
STATUS: Active
TITLE: Identical Markdown content by import/export roundtrip
STATEMENT: >>>
StrictDoc shall ensure that identical Markdown content is produced every time
StrictDoc reads a Markdown file and then writes it to another Markdown file.

The following aspects shall additionally apply:

- For MVP, line-endings should support both LF (Linux/macOS-style) and CRLF
  (Windows-style).
- The ``export --formats=markdown`` shall work for any format readable by
  StrictDoc, including Markdown itself, SDoc, RDF (future growth), ReqIF, etc.

NOTE: The write-back to Markdown file must happen through proper AST
serialization, not just by giving back the original read Markdown source.

Exceptions:

Edge cases related to handling non-default input formats are postponed after the
Markdown MVP is implemented. For example:

- Markdown reader encounters content format #3 (implicit field; see the Markdown
  Specification in spec/Markdown.md), but writer always emits #1/#2 for content
  via [LINK: SDOC-LLR-198]. In this case the content will not be identical, but
  it is accepted for an MVP implementation.
<<<
RATIONALE: >>>
A consistent import/export roundtrip implementation and testing reduces the risk
of the Markdown bi-directional import/export corruption.
<<<
RELATIONS:
- TYPE: Parent
  VALUE: SDOC-SSS-94

[REQUIREMENT]
MID: 54321111634c493dbc771ae4c8bc3b14
UID: SDOC-LLR-189
STATUS: Active
TITLE: One Markdown file — One SDoc document
STATEMENT: >>>
StrictDoc shall parse Markdown files using the "one Markdown file — one SDoc
document" principle.
<<<

[REQUIREMENT]
MID: 11133111634c493dbc771ae4c8bc3b14
UID: SDOC-LLR-190
STATUS: Active
TITLE: Reading rules — Default grammar for MVP
STATEMENT: >>>
When a parsing Markdown file, StrictDoc shall generate an SDoc document using
the default SDoc grammar according to the following rules:

- The only supported node for MVP shall be REQUIREMENT, TEXT and SECTION nodes
  with no other nodes supported.
- A valid SDoc node shall be recognized as REQUIREMENT. The Markdown's node
  title becomes the REQUIREMENT node's TITLE.
- If a Markdown node cannot be recognized as a valid SDoc node, the node shall
  recognize the said Markdown node's title as a SECTION node with a TITLE field
  set to the title and the node's body as a regular (non-normative) TEXT SDoc
  node, not as a normative SDoc node. The TEXT node's statement shall contain
  the Markdown node's body.
- All field names shall be capitalized when created to SDoc field objects. For
  example, ``Statement`` becomes ``STATEMENT``. At the same time, the original
  field names must be written to the document's grammar as-is. For example, a
  ``**Rationale**:`` becomes ``RATIONALE`` in the SDoc field name and
  ``Rationale`` in the human title.
- StrictDoc shall defer the validation of MID/UID uniqueness across nodes to the
  TraceabilityIndexBuilder class.
- If a given field name appears more than once in a node, StrictDoc shall raise
  a StrictDocSemanticError.
- If a node is otherwise invalid and also has duplicate fields, the parser shall
  treat this node as SECTION and TEXT without raising errors.
- All SDoc node fields, REQUIREMENT/TEXT/SECTION, must store all field values'
  Markdown content verbatim, without any pre-processing. This includes
  preserving original whitespace/line endings exactly.
<<<

[REQUIREMENT]
MID: c144739494ad4f75b65b9286248005eb
UID: SDOC-LLR-198
STATUS: Active
TITLE: Writing rules — Default grammar for MVP
STATEMENT: >>>
When writing an SDoc document to a markdown file, StrictDoc shall generate the
Markdown markup according to the following rules:

- The meta fields shall be written:

  - Using the format #2 for new documents not coming from file system (using backslashes for all meta-field lines but last one).
  - Using the format that was auto-detected during reading a Markdown file in case the file is already on the disk and follows a certain convention. The detection shall be detected at a file level and memorized individually by each SDoc document.

- The content fields shall be written using formats #1 (Explicit field name) for
  single-paragraph fields and #2 (Explicit field name with a line break) for
  multi-paragraph fields. A multi-paragraph field is one that results in
  multiple markdown paragraphs/blocks each separated visually by a full empty
  line.

- StrictDoc shall write the SDoc fields as Markdown fields based on SDoc human
  title as recorded in the document grammar element field human title. If a
  human title is missing in the grammar, the field name shall be used.

- All fields shall be printed in the same order like they are stored in an SDoc
  node. Meta vs content decision shall be based on a standard
  SDocNode/GrammarElement decision for multiline index.

- The node level shall be used for defining the Markdown node level. The
  document title becomes the top-level section level 1. SDoc node level 1
  becomes ``##``, level 2 becomes ``###``, etc.
<<<

[REQUIREMENT]
MID: 987111ede0f2477181bfc7667684df59
UID: SDOC-LLR-187
STATUS: Active
TITLE: Robust Markdown backend
STATEMENT: >>>
StrictDoc shall employ a well-maintained Markdown library with Python support.
<<<

[[/SECTION]]

[[SECTION]]
MID: 65cfed23d9bb404cad88dadc95feb0d1
TITLE: HTML2PDF export

[REQUIREMENT]
MID: 95f0e0198d8446a38eb1c7fc0f409522
UID: SDOC-LLR-203
TITLE: Use of html2pdf4doc
STATEMENT: >>>
StrictDoc shall export HTML documents using html2pdf4doc library with the
following document types supported already:

- StrictDoc's main DOC document type/screen.
<<<
RATIONALE: >>>
html2pdf4doc is part of the StrictDoc project that is developed by the core
team. It allows printing PDF pages directly from StrictDoc HTML and gives the
developers a full control over the printing mechanics.
<<<

[REQUIREMENT]
MID: 335b11da872245c0bf09c82d5909db0e
UID: SDOC-LLR-204
STATUS: Active
TITLE: Use of PyPDF for PDF postprocessing
STATEMENT: >>>
StrictDoc shall employ the PyPDF library for the following tasks:

- Rewriting all StrictDoc's LINK/ANCHOR to documents of the same project tree
  into the PDF anchors.
<<<
RATIONALE: >>>
The extra processing with PyPDF is needed because there are limitations of what
developers can do when printing HTML to PDF with html2pdf4doc based on Google
Chrome Driver.
<<<
RELATIONS:
- TYPE: Parent
  VALUE: SDOC-SRS-203

[REQUIREMENT]
MID: 272338e1e8f244eca573348660464b09
UID: SDOC-LLR-205
STATUS: Active
TITLE: Cross-linking PDF documents from one project tree
STATEMENT: >>>
When exporting HTML documents to PDF, StrictDoc shall rewrite all LINK/ANCHOR to
documents of the same project tree into the PDF document links/anchors according
to the following rule:

- The Chrome Driver resolves the relative links to other documents with full
  paths, e.g.,
  ``file:///<full-path-to-another-SDoc-document>-PDF.html#<anchor>``.
- The PDF postprocessing step shall convert these absolute ``file:///...` links
  to just relative paths: ``<relative-path-to-another-SDoc-document>.pdf``
  without the leading slash character.
- If one PDF is in a nested folder compared to another PDF, the link to this PDF
  anchor shall have relative ``../`` path components.
<<<
RATIONALE: >>>
Allows a reader to navigate between PDF documents of the same project as
requested by the parent requirement.
<<<
COMMENT: >>>
The PDF cross-document linking is supported by the PDF format natively but is
known to not work in all PDF viewers. For example, it is known to work well in
Linux PDF viewers, but not macOS Preview viewer.
<<<
RELATIONS:
- TYPE: Parent
  VALUE: SDOC-SRS-203

[[/SECTION]]

[[SECTION]]
MID: 7055d55c999d4c46bdfc847038a00978
TITLE: Source code parsing

[[SECTION]]
MID: e18dcfcb9b99459d9c7f560f35d01ff8
TITLE: Rust

[REQUIREMENT]
MID: d83cab2dcd014d328b348acc37c6f4a6
UID: SDOC-LLR-164
TITLE: Auto-scoped relation markers in Rust docs
STATEMENT: >>>
If a StrictDoc relation marker is inside a `Rust doc comment`_, the marker scope
shall be set to exact the item the Rust language defines as target of the
containing doc comment. The :code:`@relation(scope=...)` parameter shall
therefore be optional and shall be ignored if provided.

.. code-block:: rust
   :number-lines:

   /// @relation(REQ-1)
   impl Foo {

       /// @relation(REQ-2)
       fn foo() {
       }
   }

In the given example, the first marker shall link REQ-1 to the :code:`impl Foo`
implementation, highlighting lines 1 to 7. The second marker shall link REQ-2 to
the :code:`fn foo()` function, highlighting lines 4 to 6.

.. _Rust doc comment: https://doc.rust-lang.org/rust-by-example/meta/doc.html#doc-comments
<<<
COMMENT: >>>
Note that doc comments are syntactic sugar for `doc attribute`_ s, which shall
also be supported. To figure detailed doc comment rules from the rust-lang
specification it's sometimes useful to check for general attribute rules, if
explicit doc comment rules are missing.

.. _doc attribute: https://doc.rust-lang.org/rustdoc/write-documentation/the-doc-attribute.html
<<<
RELATIONS:
- TYPE: Parent
  VALUE: SDOC-SRS-34
- TYPE: Parent
  VALUE: SDOC-SRS-137
- TYPE: Parent
  VALUE: SDOC-SRS-204

[REQUIREMENT]
MID: 91c7b9fd9c514327bb012639cdf1515b
UID: SDOC-LLR-165
STATUS: Active
TITLE: Inner doc attributes
STATEMENT: >>>
StrictDoc shall support relation markers in inner_ `doc attribute`_ s.

.. _inner: https://doc.rust-lang.org/reference/attributes.html#r-attributes.inner
.. _doc attribute: https://doc.rust-lang.org/rustdoc/write-documentation/the-doc-attribute.html#the-doc-attribute
<<<
RELATIONS:
- TYPE: Parent
  VALUE: SDOC-SRS-204

[REQUIREMENT]
MID: 002bfab5383e4cb785049c4738651f43
UID: SDOC-LLR-166
STATUS: Active
TITLE: Inner line docs
STATEMENT: >>>
StrictDoc shall support auto-scoped relation relation markers in `inner line
docs`_.

.. _inner line docs: https://doc.rust-lang.org/reference/comments.html#grammar-INNER_LINE_DOC
<<<
RELATIONS:
- TYPE: Parent
  VALUE: SDOC-SRS-204

[REQUIREMENT]
MID: d04b97d76cc848f982610035bf7d3dc2
UID: SDOC-LLR-167
STATUS: Active
TITLE: Inner block docs
STATEMENT: >>>
StrictDoc shall support auto-scoped relation relation markers in `inner block
docs`_.

.. _inner block docs: https://doc.rust-lang.org/reference/comments.html#grammar-INNER_BLOCK_DOC
<<<
RELATIONS:
- TYPE: Parent
  VALUE: SDOC-SRS-204

[REQUIREMENT]
MID: 84b351267cfc4e16b3ff2c5db654e9f0
UID: SDOC-LLR-168
STATUS: Active
TITLE: Outer doc attributes
STATEMENT: >>>
StrictDoc shall support auto-scoped relation markers in outer_ `doc attribute`_
s.

.. _outer: https://doc.rust-lang.org/reference/attributes.html#r-attributes.outer
.. _doc attribute: https://doc.rust-lang.org/rustdoc/write-documentation/the-doc-attribute.html#the-doc-attribute
<<<
RELATIONS:
- TYPE: Parent
  VALUE: SDOC-SRS-204

[REQUIREMENT]
MID: 171978da9f8f4f40b52fb7599caa67e6
UID: SDOC-LLR-169
STATUS: Active
TITLE: Outer line docs
STATEMENT: >>>
StrictDoc shall support auto-scoped relation markers in `outer line docs`_.

.. _outer line docs: https://doc.rust-lang.org/reference/comments.html#grammar-OUTER_LINE_DOC
<<<
RELATIONS:
- TYPE: Parent
  VALUE: SDOC-SRS-204

[REQUIREMENT]
MID: 1a8d558fbe244621818b6242be365638
UID: SDOC-LLR-170
STATUS: Active
TITLE: Outer block docs
STATEMENT: >>>
StrictDoc shall support auto-scoped relation markers in `outer block docs`_.

.. _outer block docs: https://doc.rust-lang.org/reference/comments.html#railroad-OUTER_BLOCK_DOC
<<<
RELATIONS:
- TYPE: Parent
  VALUE: SDOC-SRS-204

[REQUIREMENT]
MID: e1be1f38dd374f82abd9691d081f293b
UID: SDOC-LLR-171
STATUS: Active
TITLE: File, line and range markers
STATEMENT: >>>
StrictDoc shall point to lines and line ranges of Rust code by using file, line
and range markers. These marker types shall be parsed from `regular line and
block comments`_.

Note: File markers may also result from the inner doc comments of the top-level
module.

.. _regular line and block comments: https://doc.rust-lang.org/rust-by-example/hello/comment.html#comments
<<<
RELATIONS:
- TYPE: Parent
  VALUE: SDOC-SRS-139
- TYPE: Parent
  VALUE: SDOC-SRS-124
- TYPE: Parent
  VALUE: SDOC-SRS-138
- TYPE: Parent
  VALUE: SDOC-SRS-204

[REQUIREMENT]
MID: b9b2e4d377db42f5b3fb7aeabaf3f72a
UID: SDOC-LLR-172
STATUS: Active
TITLE: Source nodes from doc comments
STATEMENT: >>>
If a Rust doc comments contains custom tags, and the containing Rust source file
matches an entry in the source node configuration, StrictDoc shall create
document nodes from the custom tags and automatically link the created node with
the Rust item targeted by the doc comment.
<<<
RELATIONS:
- TYPE: Parent
  VALUE: SDOC-SRS-141
- TYPE: Parent
  VALUE: SDOC-SRS-204

[REQUIREMENT]
MID: 9d7e371ad7a146e1968cd9bbb7a6790f
UID: SDOC-LLR-173
STATUS: Active
TITLE: Forward relations to Rust items
STATEMENT: >>>
StrictDoc shall support linking from a requirement in SDoc to a language item in
Rust code by using a :code:`FILE` relation of type :code:`FUNCTION`. For example

.. code-block:: strictdoc

   [REQUIREMENT]
   UID: REQ-1
   RELATIONS:
   - TYPE: File
     VALUE: file.rs
     FUNCTION: file::foo

This shall work for all kinds of Rust items that have a `canonical path`_,
including const, enum, fn, mod, static, struct, trait, type, union.

.. _canonical path: https://doc.rust-lang.org/reference/paths.html#canonical-paths
<<<
RELATIONS:
- TYPE: Parent
  VALUE: SDOC-SRS-204

[REQUIREMENT]
MID: d01b2204fcb44882b991ca11ce567f52
UID: SDOC-LLR-174
STATUS: Active
TITLE: Forward relation by canonical path
STATEMENT: >>>
The identifier for forward relations shall be the `canonical path`_ as the rustc
compiler would set it when invoked for a single file like

.. code-block:: shell

   rustc --crate-type rlib --emit=obj src/lib.rs

Note: :code:`cargo build` usually result in a different canonical path, since it
considers the file position relative to the crate root. Using a single file as
root is a simplification, needed because StrictDoc is unaware of the Rust file
and directory-based module hierarchy.

.. _canonical path: https://doc.rust-lang.org/reference/paths.html#canonical-paths
<<<
COMMENT: >>>
The canonical path of an item can be observed with :code:`objdump -t lib.o
--demangle=rust`. For example, given this source file

.. code-block:: rust
   :number-lines:

   pub mod foo {

       pub trait Foo {
           fn foo(&self) {}
       }

       pub struct Bar(i32);

       impl Foo for Bar {
           fn foo(&self) {}
       }
   }

:code:`objdump` will show

.. code-block:: shell

   <lib::foo::Bar as lib::foo::Foo>::foo

Alas, a forward relation would be

.. code-block:: strictdoc

   [REQUIREMENT]
   UID: REQ-1
   RELATIONS:
   - TYPE: File
     VALUE: file.rs
     FUNCTION: <lib::foo::Bar as lib::foo::Foo>::foo
<<<
RELATIONS:
- TYPE: Parent
  VALUE: SDOC-SRS-204

[REQUIREMENT]
MID: 04b5927294c34710995d3671040dd8ae
UID: SDOC-LLR-175
STATUS: Active
TITLE: Collapse doc comments
STATEMENT: >>>
Multiple scattered doc comments shall be collapsed as done by the rustdoc_ tool
when using the collapse-docs option to determine the highlight range(s).

For example, rustdoc would collapse alle these comments into the description of
:code:`fn foo()`

.. code-block:: rust
   :number-lines:

   /// Some
   /// line

   /// doc,

   /**
     * and some
     * block dock,
     */

   #[doc = "and some"]

   #[doc = "doc attr."]

   fn foo() {
   }

In the given example, the StrictDoc highlight range for the relation marker
shall be from line 1 to line 16.

.. _rustdoc: https://github.com/rust-lang/rust/tree/main/src/tools/rustdoc
<<<
RELATIONS:
- TYPE: Parent
  VALUE: SDOC-SRS-204

[REQUIREMENT]
MID: e67e8258177847138112589e606c0413
UID: SDOC-LLR-176
STATUS: Active
TITLE: Rust marker descriptions
STATEMENT: >>>
StrictDoc should use the marker labels as rustdoc_ would set them in the
description of a documented node.

.. _rustdoc: https://doc.rust-lang.org/stable/rustdoc/
<<<
RELATIONS:
- TYPE: Parent
  VALUE: SDOC-SRS-204

[REQUIREMENT]
MID: 7bf3f26c335741398a50e9679a0d4c84
UID: SDOC-LLR-177
STATUS: Active
TITLE: Valid positions of doc comments
STATEMENT: >>>
StrictDoc shall find doc comments where the language allows_ them and ignore
those in other positions.

.. _allows: https://doc.rust-lang.org/reference/attributes.html#r-attributes.allowed-position
<<<
COMMENT: >>>
Since doc comments are syntactic sugar for doc attributes, allowed position
rules for attributes apply.
<<<
RELATIONS:
- TYPE: Parent
  VALUE: SDOC-SRS-204

[REQUIREMENT]
MID: 5e9645177af14db7b5fcaba0298a328b
UID: SDOC-LLR-178
STATUS: Active
TITLE: Inner doc comments for functions
STATEMENT: >>>
StrictDoc shall find inner doc comments in function blocks.
<<<
RELATIONS:
- TYPE: Parent
  VALUE: SDOC-SRS-204

[REQUIREMENT]
MID: b70a27cc49f54b0bb7e7956b055957a4
UID: SDOC-LLR-179
STATUS: Active
TITLE: Inner doc comments for modules
STATEMENT: >>>
StrictDoc shall find inner doc comments in module blocks.
<<<
RELATIONS:
- TYPE: Parent
  VALUE: SDOC-SRS-204

[REQUIREMENT]
MID: 012e605921954430ab6c11e245fb7378
UID: SDOC-LLR-180
STATUS: Active
TITLE: Inner doc comments for external blocks
STATEMENT: >>>
StrictDoc shall find inner doc comments in external blocks.
<<<
RELATIONS:
- TYPE: Parent
  VALUE: SDOC-SRS-204

[REQUIREMENT]
MID: 2d955dd847954556aa5a32018a7c41fd
UID: SDOC-LLR-181
STATUS: Active
TITLE: Inner doc comments for implementation blocks
STATEMENT: >>>
StrictDoc shall find inner doc comments in implementation blocks.
<<<
RELATIONS:
- TYPE: Parent
  VALUE: SDOC-SRS-204

[REQUIREMENT]
MID: ef8849024b78477496620eb1bf081900
UID: SDOC-LLR-182
STATUS: Active
TITLE: Allowed position for outer docs
STATEMENT: >>>
StrictDoc shall find outer doc comments in `allowed positions`_ as specified by
the Rust language:

- All item_ declarations
- Most statements
- Block expressions, but only when they are the outer expression of an
  expression statement or the final expression of another block expression.
- Enum variants, struct and union fields
- Generic lifetime or type parameter
- Expressions in limited situations
- Function, closure and function pointer parameters

.. _allowed positions: https://doc.rust-lang.org/reference/attributes.html#r-attributes.allowed-position
.. _item: https://doc.rust-lang.org/reference/items.html#r-items.syntax
<<<
RELATIONS:
- TYPE: Parent
  VALUE: SDOC-SRS-204

[[/SECTION]]

[[SECTION]]
MID: deab09f3aa374b46a639c504267c60f9
TITLE: C

[REQUIREMENT]
MID: 5d49af5c74794e7ab0a77fe99576243c
UID: SDOC-LLR-206
TITLE: Macro definitions
STATEMENT: >>>
StrictDoc's C reader shall recognize the special macro definitions as function
definitions:

Special macro definitions:

1) The following Zephyr test macro:

.. code:: c

    ZTEST_USER(semaphore, test_sem_take_multiple) {

    }

shall be recognized as a function with a title ``ZTEST_USER(semaphore,
test_sem_take_multiple)``.

2) The following Linux syscall macro:

.. code:: c

    SYSCALL_DEFINE2(clock_gettime, const clockid_t, which_clock,
                    struct __kernel_timespec __user *, tp)
    {
        // ...
        return error;
    }

shall be recognized as a function with a title ``SYSCALL_DEFINE2(clock_gettime,
const clockid_t, which_clock, struct __kernel_timespec __user *, tp)`` with all
newlines character replaced with a space character each but all content and
punctuation preserved otherwise.
<<<

[REQUIREMENT]
MID: a06d47fd0998421a867a9de4376fdfee
UID: SDOC-LLR-207
STATUS: Active
TITLE: Forward links to macro definitions using regexes
STATEMENT: >>>
StrictDoc shall allow linking SDoc nodes to C macro definitions using regexes as
follows:

1) The forward link:

.. code:: strictdoc

    [REQUIREMENT]
    UID: ...
    STATEMENT: ...
    RELATIONS:
    - TYPE: File
      VALUE: tests/kernel/semaphore/semaphore/src/main.c
      FUNCTION: /ZTEST_USER.*semaphore.*test_k_sem_correct_count_limit/

shall match the following C source code macro definition:

.. code:: c

    ZTEST_USER(semaphore, test_sem_take_multiple) {
      // Some code
    }
<<<

[[/SECTION]]

[[SECTION]]
MID: ff6dbe210c0c471581c87be15eeaf0d2
TITLE: Modelica

[REQUIREMENT]
MID: ce516ffd17d04660a1a903306fbae0ea
UID: SDOC-LLR-219
STATUS: Draft
TITLE: Modelica classes
STATEMENT: >>>
StrictDoc shall create a language item for each Modelica class definition in a
Modelica source file.
<<<
COMMENT: >>>
Class definitions include long and short definitions, nested classes,
:code:`model extends` definitions and each class kind, for example
:code:`model`, :code:`block`, :code:`function`, :code:`package` and
:code:`record`.
<<<
RELATIONS:
- TYPE: Parent
  VALUE: SDOC-SRS-208

[REQUIREMENT]
MID: 30a76c38bfc242e1b5fb82923cb6619d
UID: SDOC-LLR-220
STATUS: Draft
TITLE: Modelica component declarations
STATEMENT: >>>
StrictDoc shall create a language item for each component declaration in the
public and protected sections of a Modelica class.
<<<
COMMENT: >>>
A declaration of several components, for example :code:`Real a, b;`, results
in one language item for each component.
<<<
RELATIONS:
- TYPE: Parent
  VALUE: SDOC-SRS-208

[REQUIREMENT]
MID: 8230f38c302a4b6c83d06851084297dd
UID: SDOC-LLR-221
STATUS: Draft
TITLE: Qualified names of Modelica items
STATEMENT: >>>
StrictDoc shall name each Modelica language item by its fully qualified
Modelica name.
<<<
COMMENT: >>>
The qualified name starts with the package name of the :code:`within` clause.
Example: the component :code:`req1Check` of the model :code:`Check` in a file
that starts with :code:`within Rig;` has the name :code:`Rig.Check.req1Check`.
<<<
RELATIONS:
- TYPE: Parent
  VALUE: SDOC-SRS-208

[REQUIREMENT]
MID: a858b2dcbc9541deae8a7f1237b92af9
UID: SDOC-LLR-222
STATUS: Draft
TITLE: Markers in Modelica description strings
STATEMENT: >>>
When the description string of a Modelica class or component contains a
relation marker, StrictDoc shall attach the relation marker to the class or
component of the description string.
<<<
COMMENT: >>>
Example:

.. code-block:: modelica

   model Check "Checks of TC-1 @relation(TC-1, scope=class)"
     Gain req2Check(k=1) "Rise check @relation(REQ-2, scope=function)";
   end Check;

The description string is the Modelica counterpart of a Python docstring.
Modelica tools keep description strings when they rewrite a file.
<<<
RELATIONS:
- TYPE: Parent
  VALUE: SDOC-SRS-208
- TYPE: Parent
  VALUE: SDOC-SRS-137

[REQUIREMENT]
MID: 148cf9de4a5d4e559a6cf170f11cc51c
UID: SDOC-LLR-223
STATUS: Draft
TITLE: Marker comment above a Modelica class
STATEMENT: >>>
When a comment ends on the line directly above a Modelica class header,
StrictDoc shall attach the relation markers of the comment to the class.
<<<
RELATIONS:
- TYPE: Parent
  VALUE: SDOC-SRS-208
- TYPE: Parent
  VALUE: SDOC-SRS-137

[REQUIREMENT]
MID: c7348e59b87d4074aa1fcf06a98c38a0
UID: SDOC-LLR-224
STATUS: Draft
TITLE: File, line and range markers in Modelica code
STATEMENT: >>>
StrictDoc shall read file, line and range markers from the line comments and
the block comments of Modelica code.
<<<
RELATIONS:
- TYPE: Parent
  VALUE: SDOC-SRS-208
- TYPE: Parent
  VALUE: SDOC-SRS-139
- TYPE: Parent
  VALUE: SDOC-SRS-124
- TYPE: Parent
  VALUE: SDOC-SRS-138

[REQUIREMENT]
MID: cbc23c71071a4f7598175b53f85071f9
UID: SDOC-LLR-225
STATUS: Draft
TITLE: Forward relations to Modelica items
STATEMENT: >>>
StrictDoc shall resolve a :code:`File` relation with a :code:`FUNCTION` or
:code:`CLASS` field to the Modelica language item with the qualified name of
the field.
<<<
COMMENT: >>>
Example:

.. code-block:: strictdoc

   [TEST_CASE]
   UID: TC-2
   RELATIONS:
   - TYPE: File
     VALUE: Rig/Check.mo
     CLASS: Rig.Check
<<<
RELATIONS:
- TYPE: Parent
  VALUE: SDOC-SRS-208

[REQUIREMENT]
MID: 221b2fe9ec63461e8bb6b1b5b39b99b8
UID: SDOC-LLR-226
STATUS: Draft
TITLE: Modelica file the parser cannot read
STATEMENT: >>>
If the Modelica parser cannot read a Modelica source file, then StrictDoc shall
read the file, line and range markers of the file without language items.
<<<
RATIONALE: >>>
With this fallback, a syntax error in one model leaves the file, line and range
markers of the file in effect.
<<<
RELATIONS:
- TYPE: Parent
  VALUE: SDOC-SRS-208

[REQUIREMENT]
MID: 0ddaf5d398fe4b3ab292f0bcb0124ca1
UID: SDOC-LLR-227
STATUS: Draft
TITLE: Warning for a Modelica file the parser cannot read
STATEMENT: >>>
If the Modelica parser cannot read a Modelica source file, then StrictDoc shall
print a warning with the path of the file and the line of the error.
<<<
RELATIONS:
- TYPE: Parent
  VALUE: SDOC-SRS-208

[[/SECTION]]

[[/SECTION]]

[[SECTION]]
MID: 6b53bbdf370f49bba360f176d607d50c
TITLE: Command-line interface

[[SECTION]]
MID: 0a3dd77d161b443c88842a53d313eb0a
TITLE: "new" command

[REQUIREMENT]
MID: 91644890fd304d86b2d756c5b1d8c9e8
UID: SDOC-LLR-208
STATUS: Active
TITLE: Create initial StrictDoc project
STATEMENT: >>>
The "new" StrictDoc CLI command shall generate a documentation skeleton that
consists of the following artifacts in the provided input directory:

- ``docs/`` folder with the following content:

  - ``high_level_requirements.sdoc`` that contains a dummy document with a requirement prefix ``HLR-`` and one high-level requirement with identifier ``HLR-1``.
  - ``low_level_requirements.sdoc`` that contains a dummy document with a requirement prefix ``LLR-`` and one low-level requirement with identifier ``LLR-1`` that has a Parent relation to the requirement ``HLR-1``.

- ``src/`` folder with the following content:

  - A source file ``main.c`` that contains a C hello world program that is annotated with a C comment that has a ``@relation`` to the ``LLR-1`` requirement.

- ``strictdoc_config.py`` that is configured to read SDoc documents from the
  ``docs/`` folder and source files from the ``src/`` folder.
- All documents must be configured with ``ENABLE_MID: True``. All nodes must
  have valid unique MID identifiers.
- At the end of the execution, the ``new`` command shall print the instructions
  for running: 1) StrictDoc's static HTML export and 2) web server.

Example of the "new" command usage:

.. code:: bash

    strictdoc new .
<<<

[[/SECTION]]

[[/SECTION]]

[[SECTION]]
MID: eb0685f50def4479b361cc475d4bd795
TITLE: Project config

[[SECTION]]
MID: 17ee741a300748f2989cd85d0638906c
TITLE: ProjectConfig

[REQUIREMENT]
MID: 50d648852d7b4dafa2a3b87779d11f7e
UID: SDOC-LLR-209
STATUS: Active
TITLE: Config rule for custom node prefix
STATEMENT: >>>
The ProjectConfig shall provide an argument/property that allows a user to
define a custom Python function where a custom node prefix can be defined for
the following combination of inputs: (node, grammar_element, document,
traceability_index, project_config).

The return value of the function shall be a prefix string.

A user shall be able to optionally revert to the default behavior in the
function implementation. Example:

.. code-block:: py

    def custom_node_prefix(
        node,
        grammar_element,
        document,
        traceability_index,
        project_config
    ):
        if document.reserved_uid == "MY_UID":
            return "MY_UID_PREFIX"
        # Default prefix.
        return None
<<<

[REQUIREMENT]
MID: 6a1cf6b5efc84fdca6a0ff5cc3f52f0c
UID: SDOC-LLR-210
STATUS: Active
TITLE: Config rule for custom node UID
STATEMENT: >>>
The ProjectConfig shall provide an argument/property that allows a user to
define a custom Python function where a node's full UID can be composed from
its resolved prefix and next available number, for the following combination
of inputs: (prefix, next_number, node, grammar_element, document,
traceability_index, project_config).

The return value of the function shall be a UID string.

A user shall be able to optionally revert to the default behavior
(``f"{prefix}{next_number}"``) in the function implementation. Example:

.. code-block:: py

    def custom_node_uid(
        prefix,
        next_number,
        node,
        grammar_element,
        document,
        traceability_index,
        project_config
    ):
        if document.reserved_uid == "MY_UID":
            return f"{prefix}{next_number:04d}"
        # Default UID.
        return None
<<<

[[/SECTION]]

[[SECTION]]
MID: e92f1e6fa2c84636a0a7c3d4d7cbe75f
TITLE: strictdoc_config.py

[REQUIREMENT]
MID: da446e6d3c6d4b13badd4a47bdbcc5a3
UID: SDOC-SRS-37
STATUS: Active
TITLE: strictdoc_config.py config file
STATEMENT: >>>
StrictDoc shall support a configuration of project-level options through a
Python file named ``strictdoc_config.py``.
<<<
RELATIONS:
- TYPE: File
  FORMAT: Sourcecode
  PATH: strictdoc/core/project_config.py
- TYPE: Parent
  VALUE: SDOC-SRS-205

[[/SECTION]]

[[/SECTION]]

[[SECTION]]
MID: b0138705e9b24886bd2792faff067410
TITLE: Assets

[REQUIREMENT]
MID: 992a734673884c4a89ada5cb1fd640c4
UID: SDOC-LLR-211
TITLE: Asset directory resolution
STATEMENT: >>>
StrictDoc shall associate a local _assets directory with every document to store
assets.

Documents shall reference assets via relative paths.
<<<
RATIONALE: >>>
- The local assets directory preserves compatibility with standard relative
  paths.
<<<

[REQUIREMENT]
MID: da0c32fb66434bcd80d959613a35a446
UID: SDOC-LLR-212
TITLE: Asset Exporting
STATEMENT: >>>
When exporting, StrictDoc shall copy the contents of the Local Asset Directories
to the output folder.

The directory structure of the assets within the output folder shall mirror
their relative structure in the source project tree to preserve relative path
integrity.
<<<

[[SECTION]]
MID: ce512ba0998d4ea1a85cfed432007922
TITLE: Image upload

[REQUIREMENT]
MID: 9413c36f26424fea9c520e4ff78e4089
UID: SDOC-LLR-218
STATUS: Active
TITLE: Supported image formats
STATEMENT: >>>
StrictDoc shall support the following image formats:

- SVG (``.svg``, ``image/svg+xml``)
- PNG (``.png``, ``image/png``)
- GIF (``.gif``, ``image/gif``)
- JPG and JPEG (``.jpg`` and ``.jpeg``, ``image/jpeg``)
- WebP (``.webp``, ``image/webp``)
- AVIF (``.avif``, ``image/avif``)

SVG is a vector format. PNG, GIF, JPG, JPEG, WebP and AVIF are raster formats.
<<<

[REQUIREMENT]
MID: 7768b2575117435e80c3b26515382b23
UID: SDOC-LLR-214
STATUS: Active
TITLE: Image upload
STATEMENT: >>>
The Web Editor shall support image upload in multi-line text fields via paste
and drag-and-drop:

1. Intercept `drop` and `paste` events and prevent default browser behaviour.
2. Accept the supported image formats defined in [LINK: SDOC-LLR-218]. Validate both the filename extension and MIME type before starting the upload.
   For every unsupported file, do not create an upload placeholder or send the file to the endpoint. Show a notification that identifies the unsupported file and lists the supported formats.
   The user shall be able to dismiss the notification with its close control or by clicking outside it.
3. Upload images asynchronously to the backend ``/actions/document/upload_asset`` endpoint, passing the current requirement MID and the active document MID along.
4. Indicate upload progress via a temporary placeholder text.
5. On success, insert an image reference at the original cursor position, following the document's markup:

   - RST: ``.. image:: ./_assets/<node_specific_subfolder>/<filename>``
   - HTML: ``<img src="./_assets/<node_specific_subfolder>/<filename>" />``
   - Markdown: ``![](./_assets/<node_specific_subfolder>/<filename>)``

   For documents configured to use RST markup, when the upload creates a vector
   and raster pair, use the wildcard filename defined in
   [LINK: SDOC-LLR-216]. If the current field already contains a direct
   reference to either file, replace that URI in its existing position.

   For documents configured to use HTML or Markdown markup, always insert a
   direct reference to each uploaded file.

6. On failure, remove the upload placeholder and show a dismissible notification
   that identifies the affected files and reports the error.
7. When an upload overwrites an image already referenced in the edited field, do
   not insert another image reference. Show a dismissible notification that
   identifies the updated file.
<<<
RATIONALE: >>>
Supports standard editor interactions and removes manual file handling,
improving usability and reducing potential for user errors.
<<<

[REQUIREMENT]
MID: 7cdd7a0838fc4212a43b336eba5ccde8
UID: SDOC-LLR-215
TITLE: Asset upload endpoint
STATEMENT: >>>
The StrictDoc web server shall provide an ``/actions/document/upload_asset``
endpoint that accepts image uploads and stores them in a node-specific
subfolder.

The endpoint shall:

1. Accept only the supported image formats defined in [LINK: SDOC-LLR-218], and
   reject unsupported files before creating directories or writing file
   contents. Reject uploads for read-only nodes (i.e. autogen).
2. Sanitize the filename by replacing spaces with underscores.
3. Validate the requirement MIDs formally
4. Use the provided Document MID to resolve the correct document relative
   ``_assets`` directory.
5. Determine the exact target subfolder based on the Asset Path Resolution
   Strategy (see [LINK: SDOC-LLR-213]).
6. Store the file in the target folder, and overwrite any existing image file
   with the same name.
7. Sync the assets to the web server so it can be served immediately.
8. When successful, return HTTP 200 with the stored filename expressed as
   relative paths.
9. When unsuccessful, return an error response.
<<<
RATIONALE: >>>
Defines a consistent and predictable storage model for image assets:

- preventing image filename collisions between requirements,
- allowing the user to update an image through re-uploading,
- allowing the user to upload images when creating a new requirement
<<<

[REQUIREMENT]
MID: 27981746203042b299b216295b6a7588
UID: SDOC-LLR-213
TITLE: Asset path resolution strategy
STATEMENT: >>>
When storing an uploaded asset, the system shall determine the correct
node-specific subfolder within the document local ``_assets`` directory based on
the following strategy:

- If the node has a permanent MID, or if MIDs are explicitly enabled in the
  document options, the subfolder shall be ``_assets/<MID>/``. (This allows
  uploads for not-yet-existing requirements when MIDs are enabled).

- Otherwise, if the node exists and has a UID, the subfolder shall be
  ``_assets/<UID>/``.

- Otherwise, if the node exists but lacks both a permanent MID and UID, the
  asset shall be stored in the document local ``_assets/`` directory.

- If the node does not yet exist and MIDs are disabled, the upload shall be
  rejected.
<<<
RATIONALE: >>>
Defines a consistent storage model that prevents image filename collisions
between requirements.

- Prioritizing the MID over the UID ensures asset paths remain stable even if a
  requirement's human-readable UID is changed later.

- When MIDs are disabled, the asset storage path depends entirely on the node's
  UID, which is only established after the node is created. Therefore, image
  upload attempts at node creation time must be rejected to prevent orphaned
  files.
<<<

[REQUIREMENT]
MID: 3157ce3de267437c8e083455fc2b1b87
UID: SDOC-LLR-216
TITLE: Support for wildcard image directive generation
STATEMENT: >>>
The ``/actions/document/upload_asset`` endpoint shall detect pairs of files that
share the same filename stem and differ only by file extension. The files may be
uploaded in a single operation or in separate operations to the same
node-specific assets location.

If such a pair consists of one raster image and one vector image, as classified
in [LINK: SDOC-LLR-218], the system shall:

- Store both files in the requirement-specific assets location.
- Return the wildcard filename
  ``./_assets/<node_specific_subfolder>/<stem>.*`` for the detected pair. The
  Web Editor shall interpret this result according to the configured document
  markup as defined in [LINK: SDOC-LLR-214].

If no such pair is detected, the system shall treat each file independently.
<<<
RATIONALE: >>>
The wildcard lets Sphinx select the vector image for HTML output and the raster
image for LaTeX/PDF output. Both files represent the same image. A raster copy
can be uploaded with the SVG or added later.
<<<

[REQUIREMENT]
MID: 82dd31e22ccf44bd8b6b924ae9591b0c
UID: SDOC-LLR-217
TITLE: Orphaned asset cleanup
STATEMENT: >>>
StrictDoc shall provide a CLI command ``strictdoc manage assets`` to identify
and remove orphaned assets.

An asset file shall be considered orphaned if it is an image file, and not
referenced by any requirement.

The command shall:

- Detect image references in nodes (for RST, HTML or Markdown).
- List image files that are not referenced by any requirement.
- Remove such orphaned files upon user request.
- When removing files, also remove empty asset folders.

The command shall inspect only asset directories discovered by
``DocumentFinder`` for the configured project input paths. Asset discovery
shall respect ``include_doc_paths`` and ``exclude_doc_paths``.

The command shall recognize ``_assets`` references with no path prefix or a
``./`` prefix.
<<<
RATIONALE: >>>
Prevents accumulation of orphaned assets. This would for instance happen if
requirement creation is aborted after already having uploaded images.
<<<

[[/SECTION]]

[[/SECTION]]
